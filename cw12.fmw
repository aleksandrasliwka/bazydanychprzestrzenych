FME workspace cw12.fmw

Parameters:
- SourceDataset_SHAPEFILE = $(FME_MF_DIR)T2019_KAR_GERMANY.zip   # Source Esri Shapefile(s)
- SourceDataset_CSV2_3 = $(FME_MF_DIR)csv.csv   # Source CSV (Comma Separated Value) File(s)
- DestDataset_JSON = $(FME_MF_DIR)koszty_poi   # Destination JSON (JavaScript Object Notation) File
- DestDataset_JSON_3 = $(FME_MF_DIR)bezkosztow_poi   # Destination JSON (JavaScript Object Notation) File
- DestDataset_FILEGDB = $(FME_MF_DIR)statystyka_koszty.gdb   # File Geodatabase
- DestDataset_FILEGDB_3 = $(FME_MF_DIR)statystyka_bezkosztow.gdb   # File Geodatabase

Readers:
- SHAPEFILE_1: SHAPEFILE from $(SourceDataset_SHAPEFILE) in LL-WGS84
- CSV2_2: CSV2 from $(SourceDataset_CSV2_3) in LL-WGS84

Writers:
- JSON_1: JSON to $(DestDataset_JSON)
- JSON_2: JSON to $(DestDataset_JSON_3)
- FILEGDB_1: FILEGDB to $(DestDataset_FILEGDB)
- FILEGDB_2: FILEGDB to $(DestDataset_FILEGDB_3)

T2019_KAR_STREETS (reader SHAPEFILE_1)
    attributes: LINK_ID long, ST_NAME char(254), REF_IN_ID long, NREF_IN_ID long, FUNC_CLASS char(1), SPEED_CAT char(1), FR_SPEED_L long, TO_SPEED_L long, DIR_TRAVEL char(1)
    -> Reprojector_4
Reprojector_4
    DEST = DHDN.Berlin/Cassini
    INTERPOLATION_TYPE_NAME = Nearest Neighbor
    RASTER_CELL_SIZE = Preserve Cells
    RASTER_TOLERANCE = 0.0
    SOURCE = Read from feature
    REPROJECTED -> bezkosztow_ShortestPathFinder [NETWORK]
    REPROJECTED -> Tester
Tester
    BOOL_OP = OR
    COMPOSITE_TEST = 1
    TEST_CLAUSE = TEST @Value(DIR_TRAVEL) = B
    TEST_MODE = TEST
    PASSED -> AttributeManager
    FAILED -> Tester_2
AttributeManager
    ATTR_TABLE:
      SET_TO forward_cost = @Evaluate(@Length()*1)
      SET_TO backward_cost = @Evaluate(@Length()*1)
    -> koszty_ShortestPathFinder [NETWORK]
Tester_2
    BOOL_OP = OR
    COMPOSITE_TEST = 1
    TEST_CLAUSE = TEST @Value(DIR_TRAVEL) = F
    TEST_MODE = TEST
    PASSED -> AttributeManager_3
    FAILED -> AttributeManager_2
AttributeManager_3
    ATTR_TABLE:
      SET_TO forward_cost = @Evaluate(@Length()*1)
      SET_TO backward_cost = @Evaluate(@Length()*9999)
    -> koszty_ShortestPathFinder [NETWORK]
AttributeManager_2
    ATTR_TABLE:
      SET_TO backward_cost = @Evaluate(@Length()*1)
      SET_TO forward_cost = @Evaluate(@Length()*9999)
    -> koszty_ShortestPathFinder [NETWORK]
CSV (reader CSV2_2)
    attributes: col0 x_coordinate, col1 y_coordinate
    -> LineBuilder
LineBuilder
    ACCUM_INPUT_ATTRS = Use Attributes From One Feature
    REMOVE_DUPLICATES = No
    LINE -> Reprojector_2
Reprojector_2
    DEST = DHDN.Berlin/Cassini
    INTERPOLATION_TYPE_NAME = Nearest Neighbor
    RASTER_CELL_SIZE = Preserve Cells
    RASTER_TOLERANCE = 0.0
    SOURCE = Read from feature
    REPROJECTED -> bezkosztow_ShortestPathFinder [FROM-TO]
    REPROJECTED -> koszty_ShortestPathFinder [FROM-TO]
bezkosztow_ShortestPathFinder: ShortestPathFinder
    ALLOW_UTURNS = Yes
    REORDER_CHOICE = None
    SNAP_POINTS = Yes
    SNAP_TOLERANCE = 200
    WEIGHT_ATTR_CHOICE = By Length
    PATH -> Bufferer
    PATH -> node_bezkosztow_SpatialFilter [Filter]
    PATH -> LengthCalculator_2
LengthCalculator_2
    DIM = 2
    LEN_ATTR = _length
    MULT = 1
    -> statystyka_bezkosztow (writer FILEGDB_2)
Bufferer
    ANGLE = 22.5
    CAP_STYLE = Round
    CORNER_STYLE = Round
    MODE = AREA
    OFFSET = 5
    OFFSET_UNITS = METERS
    BUFFERED -> poi_bezkosztow_SpatialFilter [Filter]
koszty_ShortestPathFinder: ShortestPathFinder
    ALLOW_UTURNS = Yes
    REORDER_CHOICE = None
    SNAP_POINTS = Yes
    SNAP_TOLERANCE = 200
    WEIGHT_ATTR_1 = forward_cost
    WEIGHT_ATTR_2 = backward_cost
    WEIGHT_ATTR_CHOICE = By Two Attributes
    PATH -> Bufferer_2
    PATH -> node_koszty_SpatialFilter [Filter]
    PATH -> LengthCalculator
Bufferer_2
    ANGLE = 22.5
    CAP_STYLE = Round
    CORNER_STYLE = Round
    MODE = AREA
    OFFSET = 5
    OFFSET_UNITS = METERS
    BUFFERED -> poi_koszty_SpatialFilter [Filter]
LengthCalculator
    DIM = 2
    LEN_ATTR = _length
    MULT = 1
    -> AttributeRenamer_3
AttributeRenamer_3
    ATTR_TABLE = RENAME_SET_DEFAULT _length > długość trasy
    -> statystyka_koszty (writer FILEGDB_1)
T2019_KAR_STREET_NODE (reader SHAPEFILE_1)
    attributes: NODE_ID long, LINK_ID long, POINT_NUM long, Z_LEVEL long, INTERSECT char(1), LAT double, LON double
    -> Reprojector_3
Reprojector_3
    DEST = DHDN.Berlin/Cassini
    INTERPOLATION_TYPE_NAME = Nearest Neighbor
    RASTER_CELL_SIZE = Preserve Cells
    RASTER_TOLERANCE = 0.0
    SOURCE = Read from feature
    REPROJECTED -> Tester_3
Tester_3
    BOOL_OP = OR
    COMPOSITE_TEST = 1
    TEST_CLAUSE = TEST @Value(INTERSECT) = Y
    TEST_MODE = TEST
    PASSED -> node_bezkosztow_SpatialFilter [Candidate]
    PASSED -> node_koszty_SpatialFilter [Candidate]
node_bezkosztow_SpatialFilter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
node_koszty_SpatialFilter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
T2019_KAR_POI_TABLE (reader SHAPEFILE_1)
    attributes: POI_ID long, LINK_ID long, TYPE char(250), POI_NAME char(250), ST_NAME char(250), LAT double, LON double
    -> Reprojector
Reprojector
    DEST = DHDN.Berlin/Cassini
    INTERPOLATION_TYPE_NAME = Nearest Neighbor
    RASTER_CELL_SIZE = Preserve Cells
    RASTER_TOLERANCE = 0.0
    SOURCE = Read from feature
    REPROJECTED -> poi_koszty_SpatialFilter [Candidate]
    REPROJECTED -> poi_bezkosztow_SpatialFilter [Candidate]
poi_bezkosztow_SpatialFilter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> bezkosztow_poi (writer JSON_2)
    PASSED -> StatisticsCalculator_5
    PASSED -> StatisticsCalculator_6
StatisticsCalculator_6
    COMPUTE_HISTOGRAM = NO
    COUNT_ATTR = _count
    GROUP_BY = TYPE
    PREPEND_ATTR_NAME_CHOICE = For multiple results only
    STATS_ATTRS = POI_ID
    SUMMARY -> statystyka_bezkosztow (writer FILEGDB_2)
StatisticsCalculator_5
    COMPUTE_HISTOGRAM = NO
    COUNT_ATTR = _count
    PREPEND_ATTR_NAME_CHOICE = For multiple results only
    STATS_ATTRS = TYPE
    SUMMARY -> statystyka_bezkosztow (writer FILEGDB_2)
statystyka_bezkosztow (writer FILEGDB_2)
    attributes: col0 double, col1 double, _length text(200), _count text(200), TYPE text(250)
bezkosztow_poi (writer JSON_2)
    attributes: col0 float, col1 float, POI_ID int, LINK_ID int, TYPE string, POI_NAME string, ST_NAME string, LAT float, LON float, _predicate string
poi_koszty_SpatialFilter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> koszty_poi (writer JSON_1)
    PASSED -> StatisticsCalculator
    PASSED -> StatisticsCalculator_3
StatisticsCalculator
    COMPUTE_HISTOGRAM = NO
    COUNT_ATTR = _count
    GROUP_BY = TYPE
    PREPEND_ATTR_NAME_CHOICE = For multiple results only
    STATS_ATTRS = POI_ID
    SUMMARY -> AttributeRenamer
AttributeRenamer
    ATTR_TABLE:
      RENAME_SET_DEFAULT _count > liczba poi
      RENAME_SET_DEFAULT TYPE > rodzaj poi
    -> statystyka_koszty (writer FILEGDB_1)
StatisticsCalculator_3
    COMPUTE_HISTOGRAM = NO
    COUNT_ATTR = _count
    PREPEND_ATTR_NAME_CHOICE = For multiple results only
    STATS_ATTRS = TYPE
    SUMMARY -> AttributeRenamer_2
AttributeRenamer_2
    ATTR_TABLE = RENAME_SET_DEFAULT _count > liczba wszystkich poi
    -> statystyka_koszty (writer FILEGDB_1)
statystyka_koszty (writer FILEGDB_1)
    attributes: liczba_wszystkich_poi text(200), liczba_poi text(200), rodzaj_poi text(200), długość_trasy text(200), col0 double, col1 double
koszty_poi (writer JSON_1)
    attributes: col0 float, col1 float, POI_ID int, LINK_ID int, TYPE string, POI_NAME string, ST_NAME string, LAT float, LON float, _predicate string
